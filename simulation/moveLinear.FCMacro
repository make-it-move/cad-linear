from PySide import QtCore
import time
import serial

# configure the serial connections (the parameters differs on the device you are connecting to)
ser = serial.Serial(
    port='/dev/cu.usbmodem1411',
    baudrate=9600,
    parity=serial.PARITY_ODD,
    stopbits=serial.STOPBITS_TWO,
    bytesize=serial.SEVENBITS
)

ser.open()
ser.isOpen()


from PySide import QtCore
directionMult = 1
rotationMult = 1
movement = 0
startingPos = 0
length = 450
speed = 1.8

movementTimer = QtCore.QTimer()
movementTimer.timeout.connect(MOVERAW)
rotationTimer = QtCore.QTimer()
rotationTimer.timeout.connect(ROTATERAW)


def MOVE(direction):
	global movement
	global movementTimer
	global directionMult
	global startingPos
	global ser
	
	startingPos = movement
	if direction == "L":
		directionMult = 1
	elif direction == "R":
		directionMult = -1
	if ser.isOpen():
		ser.write(direction)
	movementTimer.start(0.2)


def MOVERAW(): 
	global movement
	if (startingPos + length * directionMult == movement):
		movementTimer.stop()
	else:
		if not ((movement >= length and directionMult == 1) or (directionMult == -1 and movement <= 0)):
			movement = movement + speed * directionMult
			placement = FreeCAD.getDocument("linear_assembly_v1").getObject("Pad").Placement
			placement = App.Placement(App.Vector(0,0,movement),placement.Rotation,)
			FreeCAD.getDocument("linear_assembly_v1").getObject("Pad").Placement = placement
		else:
			movementTimer.stop()

def ROTATE(direction):
	global rotation
	global rotationTimer
	global rotationMult
	global startingRot
	global ser

	startingRot = rotation
	if direction == "L":
		rotationMult = 1
	elif direction == "R":
		rotationMult = -1
	if ser.isOpen():
		ser.write(direction)
	rotationTimer.start(0.2)


def ROTATERAW(): 
	global rotation
	rotation = rotation + speed * rotationMult
	placement = FreeCAD.getDocument("linear_assembly_v1").getObject("Pad").Placement
	placement = App.Placement(placement.Base,App.Rotation(App.Vector(0,2.5,0),rotation))
	FreeCAD.getDocument("linear_assembly_v1").getObject("Pad").Placement = placement
